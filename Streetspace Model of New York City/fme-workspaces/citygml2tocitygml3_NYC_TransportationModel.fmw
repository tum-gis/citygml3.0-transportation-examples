FME workspace citygml2tocitygml3_NYC_TransportationModel.fmw

Parameters:
- SourceDataset_CITYGML = C:\Users\chris\OneDrive\Dokumente\TUM\WS 2019-20\FME Projekte\NYC_CityGML3_test\Data\NYC_Flatiron_Streetpace_CityGML_LoD2\NYC_Flatiron_Streetpace_CityGML_LoD2\NYC_Flatiron_Streetspace_CityGML_LoD2.gml   # Source CityGML File(s)
- DestDataset_GML = C:\Users\chris\OneDrive\Dokumente\TUM\WS 2019-20\FME Projekte\NYC_CityGML3_test\Output\CityGML3_Transportation_NYC.gml   # Destination Geography Markup Language (GML) File

Readers:
- CITYGML_1: CITYGML from $(SourceDataset_CITYGML)

Writers:
- GML_1: GML to $(DestDataset_GML) in EPSG:32118

CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> AttributeCreator_4
AttributeCreator_4
    ATTR_TABLE:
      SET_TO gml_id = CityModel
      SET_TO gml_name = NYC_CityGML3_Transportation_example
    -> CityModel (writer GML_1)
CityModel (writer GML_1)
    attributes: citygml_target_uri xml_buffer, gml_description xml_buffer, gml_name xml_buffer, citygml_city_object_member{}.xlink_href xml_buffer, citygml_appearance_member{}.xlink_href xml_buffer, gml_feature_member{}.xlink_href xml_buffer
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
    -> TestFilter
Road (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
Section (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
Square (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
    -> AttributeCreator_6
AttributeCreator_6
    ATTR_TABLE = SET_TO gml_parent_id = CityModel
    -> Square (writer GML_1)
Square (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
TrafficArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, bike_lane xml_buffer, construction_status xml_buffer, curve_flag xml_buffer, entrance_area_sqm xml_buffer, entrance_street_names xml_buffer, face_code xml_buffer,
      gml_name{} xml_buffer, intersecting_segements_count xml_buffer, intersecting_segmentIDs_conc xml_buffer, intersecting_street_names_conc xml_buffer, intersection_area_sqm xml_buffer, level_end_segment xml_buffer, level_start_segment xml_buffer, number_parking_lanes xml_buffer, number_total_lanes xml_buffer, number_travel_lanes xml_buffer, parking_lot xml_buffer, parking_lot_area_sqm xml_buffer, physical_id xml_buffer, plaza_area_sqm xml_buffer, plaza_height_inch xml_buffer, plaza_height_meter xml_buffer, radius_arc xml_buffer, sanitation_district_boundary_indicator xml_buffer, segment_count xml_buffer, segment_id xml_buffer, segment_type xml_buffer, sequence_number xml_buffer, sidewalk_area_sqm xml_buffer, sidewalk_height_inch xml_buffer, sidewalk_height_meter xml_buffer, slope_percent xml_buffer, snow_priority xml_buffer, special_address_place_name xml_buffer, special_address_place_name_2 xml_buffer, special_address_place_name_3 xml_buffer,
      special_address_place_name_4 xml_buffer, special_address_place_name_5 xml_buffer, special_address_place_name_6 xml_buffer, special_address_place_name_7 xml_buffer, special_address_type xml_buffer, special_address_type_2 xml_buffer, special_address_type_3 xml_buffer, special_address_type_4 xml_buffer, special_address_type_5 xml_buffer, special_address_type_6 xml_buffer, special_address_type_7 xml_buffer, street_area_2D_meter xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_2D_meter xml_buffer, traffic_area_2D_meter xml_buffer, traffic_direction xml_buffer, traffic_direction_source xml_buffer, gml_name{0} xml_buffer, gml_name{1} xml_buffer, gml_name{2} xml_buffer, gml_name{3} xml_buffer, gml_name{4} xml_buffer,
      gml_name{5} xml_buffer, gml_name{6} xml_buffer, gml_name{7} xml_buffer, gml_name{8} xml_buffer, gml_name{9} xml_buffer, gml_name{10} xml_buffer
    -> Tester
    -> AttributeCreator_3
Tester
    BOOL_OP = OR
    TEST_CLAUSE = TEST @Value(citygml_class) = 350010
    TEST_MODE = TEST
    PASSED -> AttributeExposer
AttributeExposer
    ATTR_LIST = gml_name{}
    -> AttributeSplitter
AttributeSplitter
    ATTR_NAME = intersecting_street_names_conc
    DELIMITER = ,
    DROP_EMPTY_PARTS = Yes
    LIST_NAME = gml_name
    TRIM_OPTION = Both
    -> AttributeKeeper
AttributeKeeper
    KEEP_ATTRS = gml_name{7},gml_name{2},gml_name{6},gml_name{3},gml_name{1},gml_name,gml_name{10},gml_name{4},gml_name{5},gml_name{8},gml_name{9},gml_name{0},gml_parent_id
    -> FeatureMerger [SUPPLIER]
Intersection (writer GML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, gml_name{} xml_buffer, gml_name{0} xml_buffer, gml_name{1} xml_buffer, gml_name{2} xml_buffer, gml_name{3} xml_buffer, gml_name{4} xml_buffer,
      gml_name{5} xml_buffer, gml_name{6} xml_buffer, gml_name{7} xml_buffer, gml_name{8} xml_buffer, gml_name{9} xml_buffer, gml_name{10} xml_buffer
Track (reader CITYGML_1) [off]
    attributes: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
AuxiliaryTrafficArea (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, curb_area_sqm xml_buffer, curb_height_inch xml_buffer, curb_height_meter xml_buffer, median_area_sqm xml_buffer, median_height_inch xml_buffer, median_height_meter xml_buffer,
      median_volume_cubicmeter xml_buffer, segment_id xml_buffer, snow_priority xml_buffer
    -> AttributeCreator_3
AttributeCreator_3
    ATTR_TABLE = SET_TO citygml_lod_name = lod2MultiSurface
    -> AttributeExposer_3
AttributeExposer_3
    ATTR_LIST = gml_name,citygml_class
    -> Tester_3
ListPopulator
    LIST_NAME = gml_name
    PREFIX = gml_name
    -> AttributeExposer_4
AttributeExposer_4
    ATTR_LIST = gml_name{0}
    -> Tester_2
Tester_2
    BOOL_OP = OR
    COMPOSITE_TEST = 1
    TEST_CLAUSE = TEST @Value(citygml_feature_role) = trafficArea
    TEST_MODE = TEST
    PASSED -> GeometryExtractor
    FAILED -> GeometryExtractor_2
GeometryExtractor
    ATTR = lod2MultiSurface
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> GeometryPropertySetter
GeometryPropertySetter
    OVERWRITE_CHOICE = Yes
    REMOVE_ATTRIBUTE = No
    SETTYPE_PARAM = Traits From Attributes
    SRC_ATTRS = citygml_lod_name
    SET -> TrafficArea (writer GML_1)
TrafficArea (writer GML_1)
    attributes: citygml_lod_name xml_char(200), citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, bike_lane xml_buffer, construction_status xml_buffer, curve_flag xml_buffer, entrance_area_sqm xml_buffer, entrance_street_names xml_buffer,
      face_code xml_buffer, gml_name{} xml_buffer, intersecting_segements_count xml_buffer, intersecting_segmentIDs_conc xml_buffer, intersecting_street_names_conc xml_buffer, intersection_area_sqm xml_buffer, level_end_segment xml_buffer, level_start_segment xml_buffer, number_parking_lanes xml_buffer, number_total_lanes xml_buffer, number_travel_lanes xml_buffer, parking_lot xml_buffer, parking_lot_area_sqm xml_buffer, physical_id xml_buffer, plaza_area_sqm xml_buffer, plaza_height_inch xml_buffer, plaza_height_meter xml_buffer, radius_arc xml_buffer, sanitation_district_boundary_indicator xml_buffer, segment_count xml_buffer, segment_id xml_buffer, segment_type xml_buffer, sequence_number xml_buffer, sidewalk_area_sqm xml_buffer, sidewalk_height_inch xml_buffer, sidewalk_height_meter xml_buffer, slope_percent xml_buffer, snow_priority xml_buffer, special_address_place_name xml_buffer, special_address_place_name_2 xml_buffer,
      special_address_place_name_3 xml_buffer, special_address_place_name_4 xml_buffer, special_address_place_name_5 xml_buffer, special_address_place_name_6 xml_buffer, special_address_place_name_7 xml_buffer, special_address_type xml_buffer, special_address_type_2 xml_buffer, special_address_type_3 xml_buffer, special_address_type_4 xml_buffer, special_address_type_5 xml_buffer, special_address_type_6 xml_buffer, special_address_type_7 xml_buffer, street_area_2D_meter xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_2D_meter xml_buffer, traffic_area_2D_meter xml_buffer, traffic_direction xml_buffer, traffic_direction_source xml_buffer, gml_name{0} xml_buffer, gml_name{1} xml_buffer, gml_name{2} xml_buffer, gml_name{3} xml_buffer,
      gml_name{4} xml_buffer, gml_name{5} xml_buffer, gml_name{6} xml_buffer, gml_name{7} xml_buffer, gml_name{8} xml_buffer, gml_name{9} xml_buffer, gml_name{10} xml_buffer, curb_area_sqm xml_buffer, curb_height_inch xml_buffer, curb_height_meter xml_buffer, median_area_sqm xml_buffer, median_height_inch xml_buffer, median_height_meter xml_buffer, median_volume_cubicmeter xml_buffer, lod2MultiSurface xml_char(200)
GeometryExtractor_2
    ATTR = lod2MultiSurface
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> GeometryPropertySetter_2
GeometryPropertySetter_2
    OVERWRITE_CHOICE = Yes
    REMOVE_ATTRIBUTE = No
    SETTYPE_PARAM = Traits From Attributes
    SRC_ATTRS = citygml_lod_name
    SET -> AuxiliaryTrafficArea (writer GML_1)
AuxiliaryTrafficArea (writer GML_1)
    attributes: citygml_lod_name xml_char(200), citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, bike_lane xml_buffer, construction_status xml_buffer, curve_flag xml_buffer, entrance_area_sqm xml_buffer, entrance_street_names xml_buffer,
      face_code xml_buffer, gml_name{} xml_buffer, intersecting_segements_count xml_buffer, intersecting_segmentIDs_conc xml_buffer, intersecting_street_names_conc xml_buffer, intersection_area_sqm xml_buffer, level_end_segment xml_buffer, level_start_segment xml_buffer, number_parking_lanes xml_buffer, number_total_lanes xml_buffer, number_travel_lanes xml_buffer, parking_lot xml_buffer, parking_lot_area_sqm xml_buffer, physical_id xml_buffer, plaza_area_sqm xml_buffer, plaza_height_inch xml_buffer, plaza_height_meter xml_buffer, radius_arc xml_buffer, sanitation_district_boundary_indicator xml_buffer, segment_count xml_buffer, segment_id xml_buffer, segment_type xml_buffer, sequence_number xml_buffer, sidewalk_area_sqm xml_buffer, sidewalk_height_inch xml_buffer, sidewalk_height_meter xml_buffer, slope_percent xml_buffer, snow_priority xml_buffer, special_address_place_name xml_buffer, special_address_place_name_2 xml_buffer,
      special_address_place_name_3 xml_buffer, special_address_place_name_4 xml_buffer, special_address_place_name_5 xml_buffer, special_address_place_name_6 xml_buffer, special_address_place_name_7 xml_buffer, special_address_type xml_buffer, special_address_type_2 xml_buffer, special_address_type_3 xml_buffer, special_address_type_4 xml_buffer, special_address_type_5 xml_buffer, special_address_type_6 xml_buffer, special_address_type_7 xml_buffer, street_area_2D_meter xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_2D_meter xml_buffer, traffic_area_2D_meter xml_buffer, traffic_direction xml_buffer, traffic_direction_source xml_buffer, gml_name{0} xml_buffer, gml_name{1} xml_buffer, gml_name{2} xml_buffer, gml_name{3} xml_buffer,
      gml_name{4} xml_buffer, gml_name{5} xml_buffer, gml_name{6} xml_buffer, gml_name{7} xml_buffer, gml_name{8} xml_buffer, gml_name{9} xml_buffer, gml_name{10} xml_buffer, curb_area_sqm xml_buffer, curb_height_inch xml_buffer, curb_height_meter xml_buffer, median_area_sqm xml_buffer, median_height_inch xml_buffer, median_height_meter xml_buffer, median_volume_cubicmeter xml_buffer, lod2MultiSurface xml_char(200)

Bookmark: Filter Sections / Intersections
TestFilter
    DEFAULT_VALUE = <UNFILTERED>
    TEST_LIST = "BOOL_OP,OR,COMPOSITE_TEST,""""""<Unused>"""""",TEST_CLAUSE,TEST gml_name ATTRIBUTE_HAS_A_VALUE """,Section,"BOOL_OP,OR,COMPOSITE_TEST,""""""<Unused>"""""",TEST_CLAUSE,TEST gml_name ATTRIBUTE_IS_MISSING """,Intersection
    Section -> DuplicateFilter
    Section -> AttributeCreator_2
    Intersection -> FeatureMerger [REQUESTOR]

Bookmark: Create 1 Road Object per street name / gml id = id_streetname
DuplicateFilter
    INPUT_ORDERED_CHOICE = No
    KEYATTR = gml_name
    UNIQUE -> AttributeCreator
AttributeCreator
    ATTR_TABLE:
      SET_TO gml_id = id_@Value(gml_name)
      SET_TO gml_parent_id = CityModel
      SET_TO gml_name = @Value(gml_name)
    -> StringReplacer
StringReplacer
    CASE = NO
    FIND_TEXT = " "
    NO_MATCH = _FME_NO_OP_
    REGEXP = NO
    REPLACE_TEXT = _
    SRC_ATTRS = gml_id
    -> Road (writer GML_1)

Bookmark: Create gml_parent_id to Road objects
AttributeCreator_2
    ATTR_TABLE:
      SET_TO gml_parent_id = id_@Value(gml_name)
      SET_TO citygml_feature_role = Section
    -> AttributeExposer_2
AttributeExposer_2
    ATTR_LIST = gml_name
    -> StringReplacer_2
StringReplacer_2
    CASE = NO
    FIND_TEXT = " "
    NO_MATCH = _FME_NO_OP_
    REGEXP = NO
    REPLACE_TEXT = _
    SRC_ATTRS = gml_parent_id
    -> ListPopulator_2
ListPopulator_2
    LIST_NAME = gml_name
    PREFIX = gml_name
    -> AttributeExposer_5
AttributeExposer_5
    ATTR_LIST = gml_name{0}
    -> Section (writer GML_1)

Bookmark: Merge intersecting street names for intersections
FeatureMerger
    ATTR_ACCUM_MODE = Merge Supplier
    ATTR_CONFLICT_RES = Use Requestor
    IGNORE_NULLS = No
    JOIN_KEYS = @Value(gml_id) @Value(gml_parent_id) AUTO
    MERGE_TYPE = Attributes Only
    PROCESS_DUPS = NO
    REJECT_NULL_MISSING_KEYS = No
    SUPPLIERS_FIRST = No
    MERGED -> AttributeCreator_5

Bookmark: Create gml_parent_id to 1 Road obejct
AttributeCreator_5
    ATTR_TABLE:
      SET_TO citygml_feature_role = Intersection
      SET_TO gml_parent_id = id_@Value(gml_name{0})
    -> StringReplacer_3
StringReplacer_3
    CASE = NO
    FIND_TEXT = " "
    NO_MATCH = _FME_NO_OP_
    REGEXP = NO
    REPLACE_TEXT = _
    SRC_ATTRS = gml_parent_id
    -> Intersection (writer GML_1)

Bookmark: Filter Tracks
Tester_3
    BOOL_OP = OR
    COMPOSITE_TEST = 1
    TEST_CLAUSE = TEST @Value(citygml_class) = 380010
    TEST_MODE = TEST
    FAILED -> ListPopulator
