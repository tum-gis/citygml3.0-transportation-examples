FME workspace C_citygml2tocitygml3_transportation.fmw

Parameters:
- DestDataset_GML_3 = $(FME_MF_DIR)Output\cityGML3_transportation_simpleIntersection.gml   # Destination Geography Markup Language (GML) File
- SourceDataset_CITYGML_3 = $(FME_MF_DIR)Output\cityGML2_transportation_simpleIntersection.gml   # Source CityGML File(s)

Readers:
- CITYGML_2: CITYGML from $(SourceDataset_CITYGML_3)

Writers:
- GML_1: GML to $(DestDataset_GML_3)

Bookmark: CityModel
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
    -> AttributeCreator_2
AttributeCreator_2
    ATTR_TABLE:
      SET_TO gml_id = CityModel
      SET_TO gml_name = CityGML3_Transportation_simpleIntersection_granularity_way
    -> CityModel (writer GML_1)
CityModel (writer GML_1)
    attributes: gml_name xml_buffer, citygml_target_uri xml_buffer, gml_description xml_buffer, citygml_city_object_member{}.xlink_href xml_buffer, citygml_appearance_member{}.xlink_href xml_buffer, gml_feature_member{}.xlink_href xml_buffer

Bookmark: Input CityGML2
Road (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, gml_pare_1 xml_buffer, gml_parent xml_buffer
    -> DuplicateFilter
    -> ListPopulator_2
TrafficArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer
    -> AttributeCreator_6

Bookmark: Create CityGML3 Road objects
DuplicateFilter
    INPUT_ORDERED_CHOICE = No
    KEYATTR = gml_parent
    UNIQUE -> ListPopulator_3
ListPopulator_3
    LIST_NAME = gml_name
    PREFIX = gml_name
    -> AttributeExposer_3
AttributeExposer_3
    ATTR_LIST = gml_name{0}
    -> AttributeCreator
AttributeCreator
    ATTR_TABLE:
      SET_TO gml_id = @Value(gml_parent)
      SET_TO gml_parent_id = CityModel
      SET_TO citygml_feature_role = Road
      SET_TO xlink_href = id_Intersection_AB
      SET_TO citygml_lod_name = lod2MultiSurface
    -> Tester
Tester
    BOOL_OP = OR
    COMPOSITE_TEST = 1
    TEST_CLAUSE = TEST @Value(gml_id) = id_Road_A
    TEST_MODE = TEST
    PASSED -> AttributeCreator_7
    FAILED -> AttributeCreator_8
AttributeCreator_7
    ATTR_TABLE = SET_TO gml_name = Road_A
    -> AttributeKeeper
AttributeCreator_8
    ATTR_TABLE = SET_TO gml_name = Road_B
    -> AttributeKeeper
AttributeKeeper
    KEEP_ATTRS = gml_parent_id,gml_id,gml_name,citygml_lod_name,xlink_href
    -> Road (writer GML_1)
    -> Road

Bookmark: Output CityGML3
Road: Inspector
Road (writer GML_1)
    attributes: gml_name xml_buffer
Intersection: Inspector
Intersection (writer GML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, gml_pare_1 xml_buffer, gml_parent xml_buffer, gml_name{} xml_char(200), gml_name{0} xml_char(200), gml_name{1} xml_char(200), gml_name{2} xml_char(200),
      gml_name{3} xml_char(200), gml_name{4} xml_char(200), gml_name{5} xml_char(200), gml_name{6} xml_char(200), gml_name{7} xml_char(200), gml_name{8} xml_char(200), gml_name{9} xml_char(200), gml_name{10} xml_char(200)
Section: Inspector
Section (writer GML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, gml_pare_1 xml_buffer, gml_parent xml_buffer, gml_name{} xml_char(200), gml_name{0} xml_char(200), gml_name{1} xml_char(200), gml_name{2} xml_char(200),
      gml_name{3} xml_char(200), gml_name{4} xml_char(200), gml_name{5} xml_char(200), gml_name{6} xml_char(200), gml_name{7} xml_char(200), gml_name{8} xml_char(200), gml_name{9} xml_char(200), gml_name{10} xml_char(200)
TrafficArea: Inspector
TrafficArea (writer GML_1)
    attributes: citygml_lod_name xml_char(200), citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, gml_name{} xml_char(200), gml_name{0} xml_char(200), gml_name{1} xml_char(200), gml_name{2} xml_char(200), gml_name{3} xml_char(200),
      gml_name{4} xml_char(200), gml_name{5} xml_char(200), gml_name{6} xml_char(200), gml_name{7} xml_char(200), gml_name{8} xml_char(200), gml_name{9} xml_char(200), gml_name{10} xml_char(200), lod2MultiSurface xml_buffer

Bookmark: Filter Sections / Intersection
ListPopulator_2
    LIST_NAME = gml_name
    PREFIX = gml_name
    -> AttributeExposer_2
AttributeExposer_2
    ATTR_LIST = gml_name{0}
    -> AttributeCreator_3
AttributeCreator_3
    ATTR_TABLE = SET_TO gml_parent_id = @Value(gml_parent)
    -> Tester_2
Tester_2
    BOOL_OP = OR
    COMPOSITE_TEST = 1
    TEST_CLAUSE = TEST @Value(gml_id) = id_intersection_AB
    TEST_MODE = TEST
    PASSED -> AttributeCreator_5
    FAILED -> AttributeCreator_4

Bookmark: Create Intersections
AttributeCreator_5
    ATTR_TABLE:
      SET_TO citygml_feature_role = Intersection
      SET_TO citygml_lod_name = lod2MultiSurface
    -> Intersection
    -> Intersection (writer GML_1)

Bookmark: Create Sections
AttributeCreator_4
    ATTR_TABLE:
      SET_TO citygml_feature_role = Section
      SET_TO citygml_lod_name = lod2MultiSurface
    -> Section
    -> Section (writer GML_1)

Bookmark: Create CityGML3 TrafficAreas / set geometry
AttributeCreator_6
    ATTR_TABLE:
      SET_TO citygml_lod_name = lod2MultiSurface
      SET_TO citygml_feature_role = bounded_by
    -> ListPopulator
ListPopulator
    LIST_NAME = gml_name
    PREFIX = gml_name
    -> AttributeExposer_4
AttributeExposer_4
    ATTR_LIST = gml_name{0}
    -> GeometryExtractor
GeometryExtractor
    ATTR = lod2MultiSurface
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> GeometryPropertySetter
GeometryPropertySetter
    OVERWRITE_CHOICE = Yes
    REMOVE_ATTRIBUTE = No
    SETTYPE_PARAM = Traits From Attributes
    SRC_ATTRS = citygml_lod_name
    SET -> TrafficArea (writer GML_1)
    SET -> TrafficArea
