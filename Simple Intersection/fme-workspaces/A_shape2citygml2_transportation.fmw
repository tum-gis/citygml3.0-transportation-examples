FME workspace A_shape2citygml2_transportation.fmw

Parameters:
- SourceDataset_ESRISHAPE = $(FME_MF_DIR)Input\Input_neu\Sections_neu.shp   # Source Esri Shapefile(s)
- SourceDataset_ESRISHAPE_5 = $(FME_MF_DIR)Input\Input_neu\Intersections_neu.shp   # Source Esri Shapefile(s)
- SourceDataset_ESRISHAPE_7 = $(FME_MF_DIR)Input\Input_neu\Footpath_neu.shp   # Source Esri Shapefile(s)
- SourceDataset_ESRISHAPE_6 = $(FME_MF_DIR)Input\Input_neu\Carriageway_neu.shp   # Source Esri Shapefile(s)
- DestDataset_CITYGML = $(FME_MF_DIR)Output\cityGML2_Transportation_simpleIntersection.gml   # Destination CityGML Document

Readers:
- ESRISHAPE_1: ESRISHAPE from $(SourceDataset_ESRISHAPE)
- ESRISHAPE_2: ESRISHAPE from $(SourceDataset_ESRISHAPE_5)
- ESRISHAPE_3: ESRISHAPE from $(SourceDataset_ESRISHAPE_7)
- ESRISHAPE_4: ESRISHAPE from $(SourceDataset_ESRISHAPE_6)

Writers:
- CITYGML_1: CITYGML to $(DestDataset_CITYGML)

Road: Inspector
Road (writer CITYGML_1)
    attributes: gml_name xml_buffer, gml_parent xml_char(50), gml_pare_1 xml_char(200)
CoordinateSystemSetter_3
    COORDSYS = EPSG:25832
    -> 3DForcer_2
3DForcer_2
    KEEPZVAL = No
    ZVALATTR = 0
    -> AttributeCreator_5
AttributeCreator_5
    ATTR_TABLE:
      SET_TO gml_parent_id = @Value(gml_parent)
      SET_TO citygml_lod_name = lod2MultiSurface
      SET_TO citygml_feature_role = traffficArea
    -> AttributeKeeper_4
AttributeKeeper_4
    KEEP_ATTRS = gml_name,citygml_lod_name,citygml_feature_role,gml_id,gml_parent_id
    -> Orientor
Orientor
    KIND = LEFT_HAND_RULE
    ORIENTED -> CityGMLGeometrySetter
CoordinateSystemSetter_4
    COORDSYS = EPSG:25832
    -> 3DForcer
3DForcer
    KEEPZVAL = No
    ZVALATTR = 0
    -> AttributeCreator_6
AttributeCreator_6
    ATTR_TABLE:
      SET_TO gml_parent_id = @Value(gml_parent)
      SET_TO citygml_lod_name = lod2MultiSurface
      SET_TO citygml_feature_role = trafficArea
    -> AttributeKeeper_5
AttributeKeeper_5
    KEEP_ATTRS = gml_name,citygml_lod_name,citygml_feature_role,gml_id,gml_parent_id
    -> Orientor_2
Orientor_2
    KIND = LEFT_HAND_RULE
    ORIENTED -> CityGMLGeometrySetter
CityGMLGeometrySetter
    GEOM = lod2MultiSurface
    ROLE = trafficArea
    -> TrafficArea (writer CITYGML_1)
    -> trafficArea
trafficArea: Inspector
TrafficArea (writer CITYGML_1)
    attributes: citygml_feature_role xml_buffer, gml_name xml_buffer

Bookmark: CityModel
Creator
    GEOMTYPE = Geometry Object
    NUM = 1
    CREATED -> AttributeCreator_2
AttributeCreator_2
    ATTR_TABLE:
      SET_TO gml_id = CityModel
      SET_TO gml_name = CityGML2_Transportation_simpleIntersection_granularity_way
    -> CityModel (writer CITYGML_1)
CityModel (writer CITYGML_1)
    attributes: gml_name xml_buffer, _creation_instance xml_char(200)

Bookmark: Input .shp
Sections_neu (reader ESRISHAPE_1)
    attributes: gml_id char(50), gml_name char(50), gml_parent char(50)
    -> CoordinateSystemSetter
Intersections_neu (reader ESRISHAPE_2)
    attributes: gml_id char(50), gml_name char(50), gml_parent char(50), gml_pare_1 char(50)
    -> CoordinateSystemSetter_2
Footpath_neu (reader ESRISHAPE_3)
    attributes: Id long, gml_parent char(50), gml_id char(50), gml_name char(50)
    -> CoordinateSystemSetter_3
Carriageway_neu (reader ESRISHAPE_4)
    attributes: Id long, gml_parent char(50), gml_id char(50), gml_name char(50)
    -> CoordinateSystemSetter_4

Bookmark: Create Sections (and write to Road objects in CityGML2)
CoordinateSystemSetter
    COORDSYS = EPSG:25832
    -> GeometryRemover_2
GeometryRemover_2
    -> AttributeCreator_3
AttributeCreator_3
    ATTR_TABLE:
      SET_TO gml_parent_id = @Value(gml_parent)
      SET_TO citygml_feature role = Section
    -> AttributeKeeper_2
AttributeKeeper_2
    KEEP_ATTRS = gml_name,gml_parent,gml_id,gml_parent_id
    -> Road (writer CITYGML_1)
    -> Road

Bookmark: Create Intersection (and write to Road object in CityGML2 )
CoordinateSystemSetter_2
    COORDSYS = EPSG:25832
    -> GeometryRemover_3
GeometryRemover_3
    -> AttributeCreator_4
AttributeCreator_4
    ATTR_TABLE:
      SET_TO gml_parent_id = @Value(gml_parent)
      SET_TO citygml_feature_role = Intersection
    -> AttributeKeeper_3
AttributeKeeper_3
    KEEP_ATTRS = gml_name,gml_pare_1,gml_parent,gml_id,gml_parent_id
    -> Road (writer CITYGML_1)
    -> Road
